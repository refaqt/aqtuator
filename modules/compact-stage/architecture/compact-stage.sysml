// The compact stage: its requirements, its parts, and the interfaces between
// its parts.
//
// Requirements: STG-01 to STG-15 hold for the whole stage: its size, its
// accuracy, its speed, its force and its load. A design review or a
// measurement campaign can cite each one by its short name. The servo drive
// has its own requirements in motor-drive.sysml.
//
// Rule for a pass or a fail: a bought part (a guide, a motor, an encoder)
// passes only on the deciding number in the maker's own data sheet or
// manual. A trade article, a shop page or a search result is not enough.
// See docs/mistakes/2026-09-29_loop-rate-from-a-trade-article.md.
//
// Every error value is a half band: "5 µm" means "within +/- 5 µm".
//
// Structure:
//
// The compact stage is one assembly of five parts that we make:
//
//   compact-stage
//     base             the fixed body; it mounts on the machine
//     carriage-bottom  the moving part inside the base
//     carriage-top     the moving part above the base; the load mounts on it
//     sealing-strip    a strip that closes the slot in the top of the base;
//                      six M4 screws hold it on the base
//
// The CAD of each part is in cad/parts/<part>/. The assembly is in
// cad/assemblies/compact-stage/.
//
// Rule: every pair of parts that touch has an interface. The interface is a
// port def below, a port on each part (the plain port on one side, the
// conjugate ~ port on the other), and a connection in CompactStage. The
// version is part of the name: a change that no longer fits the old part is
// a new version (_v2), not an edit of _v1.
//
// Bought parts come from the parts library in modules/stoq/. The two guide
// rails and the two magnet tracks (stators) of the linear motor are in this
// file, with their interfaces to the base. The four guide blocks and the
// forcer (the coil part of the motor) are in this file, with their
// interfaces to carriage-bottom. The linear encoder is in this file too: the
// read head on carriage-bottom, the scale on the base.
// The eight seal strip rollers are in this file, with their interface to
// the carriage halves. Each roller is an assembly of standard parts and one
// sleeve we make. See docs/decisions/2026-10-28_seal-strip-rollers-on-flanged-ball-bearings.md.
// Not modelled yet: the screws, and the interface between a roller and the
// sealing strip.
//
// Not modelled yet either: the interface between a guide block and its
// rail. It needs a choice first: which row of blocks (a or b) runs on the
// reference rail.
//
// The interfaces below say what joins what. Most hold no dimensions yet.
// Add a dimension when the CAD fixes it, and keep it the same in both.
package CompactStage {
    private import ScalarValues::*;
    private import ISQ::*;
    private import SI::*;

    // ---------------------------------------------------------------------
    // Interfaces to the outside. These are the interfaces of the whole
    // module, and okh.toml lists them too, under [[provides-interface]].
    // ---------------------------------------------------------------------

    port def BaseMountInterface_v1 {
        doc /*
         * The bottom face of the base, where the stage screws onto the
         * machine. The screw holes follow the grid of STG-14.
         *
         * Twelve M5 screws go down through the base. The clearance holes
         * are 5.5 mm, in two rows along the travel: y = 5 mm and
         * y = 205 mm, so the rows are 200 mm apart. In each row, six holes
         * sit at x = 20 mm to 420 mm, 80 mm apart. Each hole has a slot
         * from the top down to the 10 mm floor for the screw head.
         *
         * The bottom face has a 0.5 mm recess from y = 40 mm to
         * y = 170 mm. Only the two outer strips, 40 mm wide, touch the
         * machine. So the base does not rock on a surface that is not
         * perfectly flat.
         */
        attribute holePitch : LengthValue = 80 [mm];        // along the travel
        attribute rowDistance : LengthValue = 200 [mm];     // across the travel
        attribute screwCount : Natural = 12;
    }

    port def CarriageMountInterface_v1 {
        doc /*
         * The top face of carriage-top, where the load screws onto the
         * stage. The screw holes follow the grid of STG-14.
         *
         * Twelve M5 threaded holes, blind, from the top face. They sit in
         * four rows at x = -100, -80, 80 and 100 mm from the carriage
         * centre. In each row, the holes sit at y = -80 mm, 0 and 80 mm.
         * The outer rows (x = -100 and 100 mm, 200 mm apart) match the
         * base holes (BaseMountInterface_v1) of a second stage turned by
         * 90 degrees, so two stages make a cross table. The upper base
         * then sits 40 mm off the carriage centre, along its own travel.
         * The inner rows are 20 mm inside the outer rows.
         *
         * Thread depths, limited by the pockets underneath:
         * - outer rows, y = 0: 10 mm of thread (13 mm drill).
         * - outer rows, corners: 6 mm of thread (7 mm drill), because the
         *   roller pockets leave 8.5 mm of material.
         * - inner rows: 9 mm of thread (11 mm drill), because a recess in
         *   the bottom face leaves 14 mm of material.
         * Use M5 screws that reach no deeper than the thread.
         *
         * The middle of the top face has a 0.5 mm recess, 150 mm by
         * 150 mm. The load only touches the face around it, where the
         * screw holes are.
         */
        attribute holePitch : LengthValue = 80 [mm];        // across the travel
        attribute rowDistance : LengthValue = 200 [mm];     // outer rows, along the travel
        attribute innerRowDistance : LengthValue = 160 [mm]; // inner rows, along the travel
        attribute screwCount : Natural = 12;
    }

    // ---------------------------------------------------------------------
    // Interfaces between the parts of the stage
    // ---------------------------------------------------------------------

    port def CarriageJointInterface_v1 {
        doc /*
         * carriage-bottom and carriage-top screw together, and move as one
         * body. carriage-bottom is screwed onto the guide blocks. It has no
         * connection with the base.
         *
         * The sealing strip runs through the carriage, over carriage-bottom
         * and under carriage-top. The strip never touches either carriage
         * half, so the strip has no interface with them. Only the rollers
         * in the carriage touch the strip. They are bought parts and come
         * later.
         *
         * The two side strips of carriage-bottom (11 mm wide) sit in the
         * two side pockets under carriage-top. The top of each strip
         * touches the ceiling of its pocket. Over the middle of
         * carriage-bottom, carriage-top stays 2 mm higher. The ends of
         * carriage-top stay 0.5 mm above the base.
         *
         * Six M4 screws go down through carriage-top into carriage-bottom:
         * three in the middle of each side strip, 74.1 mm apart along the
         * travel, the middle one at the centre of the carriage. Each hole
         * in carriage-top has a counterbore for the screw head. In
         * carriage-bottom the holes are threaded and blind, 9 mm deep,
         * because the base is only 0.5 mm under the strips. Use M4x12
         * screws (ISO 4762): about 8 mm of the screw goes into the thread.
         * A screw longer than 12 mm can touch the bottom of the hole.
         *
         * There is no screw in the middle of the carriage. The sealing
         * strip runs there, in the 2 mm gap between the two halves.
         *
         * In the CAD, the frame IF_carriage_joint sits on the contact
         * plane, at the centre of the carriage, in both parts. Z points
         * up, from carriage-bottom into carriage-top. X runs along the
         * travel, towards the start of the carriage. The two frames are
         * the same place, so the joint needs no offset.
         */
        attribute holePitch : LengthValue = 74.1 [mm];      // along the travel
        attribute screwCount : Natural = 6;
    }

    port def BlockMountInterface_v1 {
        doc /*
         * A guide block screws to the bottom face of carriage-bottom. The
         * block sits in a pocket. Its top face touches the floor of the
         * pocket. Two M4 screws go down through the carriage into the
         * threaded holes of the block. Each hole has a counterbore on the
         * top face of the carriage for the screw head.
         *
         * The carriage has four blocks, in two rows along the travel.
         * Row a is at x = 35 mm in the carriage, row b at x = 173 mm.
         * "Start" is the end of the carriage where the motor cable leaves
         * (y = 21 mm), "end" is the other end (y = 159 mm). The names do
         * not say which row runs on the reference rail.
         *
         * The lubrication unit (E2) of each block points out of the
         * carriage, away from its centre.
         *
         * In the CAD, the frames IF_block_a_start_mount,
         * IF_block_b_start_mount, IF_block_a_end_mount and
         * IF_block_b_end_mount sit on the floor of each pocket, at the
         * centre of the two holes. Z points down, into the block. X runs
         * along the rail, from the end of the carriage towards its
         * centre. They join the frame IF_mount_top of the block.
         */
        attribute holePitch : LengthValue = 26 [mm];        // across the rail
        attribute holesPerBlock : Natural = 2;
    }

    port def ForcerMountInterface_v1 {
        doc /*
         * The forcer of the linear motor screws to the bottom face of
         * carriage-bottom. It sits in a pocket between the rows of guide
         * blocks, with its coils facing down, towards the magnet tracks.
         * The hole pattern sits 16 mm off the centre of the carriage,
         * away from the cable end. That leaves room for a slot for the
         * motor cable.
         * Six M4 screws go down through the carriage into the threaded
         * holes of the forcer. The screw length is not chosen yet.
         *
         * The holes are in two rows along the travel. The cable end of
         * the forcer points to the start of the carriage, where the cable
         * slot is.
         *
         * In the CAD, the frame IF_forcer_mount sits on the floor of the
         * pocket, on the middle hole, halfway between the rows. Z points
         * down, into the forcer. X runs along the travel, away from the
         * cable end. It joins the frame IF_mount_top of the forcer.
         */
        attribute holePitch : LengthValue = 35 [mm];        // along the travel
        attribute rowSpacing : LengthValue = 50 [mm];
        attribute holesPerRow : Natural = 3;
    }

    port def SlotSealInterface_v1 {
        doc /*
         * The sealing strip lies in a pocket 0.15 mm deep in the top of the
         * base, so its top is level with the top of the base. It closes the
         * slot along the whole travel. Magnets in a 3 mm wide ring pocket,
         * 0.5 mm below the strip pocket, hold it down around the slot. The
         * ring is cut in two at each preload screw.
         *
         * The pocket is 186 mm wide over the strip body, the strip 185.6 mm:
         * 0.2 mm on each side, and also 0.2 mm on each side to the 186 mm
         * slope openings of the carriage.
         */
        attribute pocketDepth : LengthValue = 0.15 [mm];
    }

    port def MagnetRingInterface_v1 {
        doc /*
         * The ring pocket for the magnet strips, in the floor of the strip
         * pocket: 3 mm wide, 0.5 mm deep, R4 outer corners. It is cut in two
         * at each preload screw. Ten straight strips lie in it: one 417.5 mm
         * strip on each long side, and four 21.5 mm strips in each end leg.
         * In the end legs the floor has holes (a cavity at each corner and
         * the damper slots), so each short strip sits on one piece of solid
         * floor. The strips lie adhesive face down on the ring floor, and
         * their top is level with the floor of the strip pocket.
         *
         * Base frame IF_magnet_* at a corner of the adhesive face of each
         * strip, Z up, X along the strip. It joins the frame IF_end of the
         * strip. "start" is the low-x end of the base, a the low-y side, 1
         * the piece nearest the corner.
         */
        attribute ringWidth : LengthValue = 3 [mm];
        attribute ringDepth : LengthValue = 0.5 [mm];
    }

    port def StripScrewInterface_v1 {
        doc /*
         * Six M4 screws hold the sealing strip on the base. The holes are
         * tapped M4, 12 mm deep, in the floor of the strip pocket.
         *
         * Preload: one countersunk screw ISO 10642 M4 x 10 at each strip end,
         * on the middle line (base holes 6.5 mm from each base end). The
         * strip hole (5 mm) sits 0.35 mm off the screw axis, towards the
         * strip middle. Tightening the screw pushes the outer edge of the
         * hole outwards, so the strip is pulled. Both ends together move
         * 0.21 mm for the design pull of 270 N. See
         * simulation/cases/strip-seal-fit/.
         *
         * Clamp: one button head screw with collar ISO 7380-2 M4 x 10 at
         * each corner (base holes 5 mm from the end, 8 mm from the side).
         * Strip holes 4.5 mm. Tighten them when the pull is set, then take
         * the two preload screws out. The corner screws then hold the pull.
         */
        attribute pull : ForceValue = 270 [N];
    }

    port def RailMountInterface_v1 {
        doc /*
         * A guide rail lies on the floor of the base. The floor is 3 mm
         * below the tops of the tabs. M4 screws go through the rail from
         * above into threaded holes in the base. The holes go through the
         * 10 mm floor. Use M4 x 16 screws: they engage 6.3 mm of thread.
         * The M4 x 20 screw that HIWIN lists would come out of the bottom
         * face by 0.3 mm.
         *
         * The tabs stand out from the side wall of the base, and the
         * reference rail lies against them with its outer side. Its inner
         * side touches nothing. Each tab is 20 mm long and starts 19 mm in
         * from the end of the rail, so it never touches the rail end. The
         * rounded corners at the foot of each tab stay 4.5 mm away from the
         * rail.
         *
         * The reference rail (y = 174 mm) lies against two tabs, one near
         * each end. The tabs set its position and its direction.
         *
         * The second rail (y = 36 mm) has no tab. Both of its sides touch
         * nothing. The carriage sets its position and its direction: put
         * the carriage on both rails and move it from end to end while you
         * tighten the screws of the second rail, one after the other. HIWIN
         * calls this "alignment on the reference rail". A tab at the second
         * rail would fight the carriage, so there is none.
         *
         * The y positions are rail centres, measured from the long side of
         * the base. The rails are 138 mm apart, the same as the rows of
         * guide blocks in carriage-bottom. The first hole is 40 mm from
         * the end of the base.
         *
         * The base is 210 mm wide. The pocket between the side walls is
         * 176 mm wide, so each wall is 17 mm thick. Each guide block has
         * 2 mm of space to the wall. The tabs follow the reference
         * rail: in the CAD, their depth is a formula of the rail position.
         *
         * In the CAD, the base has the frames IF_reference_rail_mount and
         * IF_second_rail_mount. Each sits on the floor (z = 10 mm), on the
         * first hole of its rail. X runs along the rail, Z points up. A
         * Fixed joint to the frame IF_mount_bottom of the rail puts the
         * rail from x = 11 mm to x = 429 mm.
         */
        attribute holePitch : LengthValue = 60 [mm];
        attribute firstHoleOffset : LengthValue = 40 [mm];
        attribute railSpacing : LengthValue = 138 [mm];
        attribute holesPerRail : Natural = 7;
        attribute screwLength : LengthValue = 16 [mm];   // M4 x 16
    }

    port def StatorMountInterface_v1 {
        doc /*
         * A magnet track (stator) of the linear motor lies with its bottom
         * face on the floor of the base, between the two guide rails.
         * Screws go through the 5.5 mm holes of the stator into threaded
         * M5 holes in the base. The holes go through the 10 mm floor.
         *
         * Each stator has two rows of three holes. The rows are 74 mm
         * apart, on both sides of the centre line of the base. In a row,
         * the holes are 60 mm apart. The Maxwell data sheet drawing says
         * "A x 120" here. That is wrong: the holes are 60 mm apart.
         *
         * The two stators lie end to end, both with their N end towards
         * the start of the base. Their ends are cut at a slant, and they
         * fit into each other. The first hole of the first stator is
         * 70 mm from the start of the base. The second stator starts
         * 180 mm further on, the length LC of one stator.
         *
         * The stators are aligned with locating pins, not with milled
         * edges, so that stators of other lengths fit too. The pin holes
         * are not modelled yet. The screw length is not chosen yet.
         *
         * In the CAD, the frame IF_mount_bottom of the stator sits on its
         * first hole, at the N end, halfway between the rows.
         */
        attribute holePitch : LengthValue = 60 [mm];
        attribute rowSpacing : LengthValue = 74 [mm];
        attribute holesPerRow : Natural = 3;
        attribute statorPitch : LengthValue = 180 [mm];
    }

    port def ReadheadMountInterface_v2 {
        doc /*
         * The read head of the linear encoder screws to the bottom of
         * carriage-bottom. It hangs in a pocket on the side of the second
         * rail, with its scanning face towards the side wall of the base.
         * The 13.5 mm side face of the head touches the ceiling of the
         * pocket. The cable leaves the head towards the end of the base
         * (-X), the way the pocket leaves room for it.
         *
         * The pocket is 16 mm deep and the head is 13.5 mm, so the head
         * sits 2.5 mm inside the carriage. It stays 1 mm away from the
         * base and 4 mm away from the second rail. The pocket is 38 mm
         * long, and the head is 36 mm long and centred in it: 1 mm of
         * space at each end.
         *
         * Two M3 screws go down through the carriage into the head. The
         * two holes of the head are M3 threads through its full 13.5 mm.
         * Each hole in the carriage has a counterbore on its top face.
         * The screw passes 8.1 mm of carriage, so an M3 x 16 screw has
         * about 7.9 mm of thread in the head. RSF allows at most 1.2 Nm
         * (AK MC 15 mounting instructions, page 9). The parts library
         * reads at least 4 mm of thread from page 10; that page is a
         * drawing and was not checked again here.
         *
         * The holes are 26 mm apart, as in the head (RSF drawing
         * D1158017-04). Their axes are 3.0 mm from the step face of the
         * carriage at x = 17 mm (Sketch031 readhead_hole_inset). In the
         * head they are 3 mm from the scanning face, so the scanning face
         * is flush with the step face. That gives the gap of
         * ScaleReadInterface_v2. Along the travel, the midpoint of the
         * holes is 1 mm from the middle of the pocket, because the holes
         * are 4 mm and 6 mm from the two ends of the head. The holes are
         * 3.4 mm, so the head can move 0.2 mm each way: set the gap with
         * the 0.55 mm gap foil that comes with the head before you
         * tighten the screws.
         *
         * In the CAD, the frame IF_readhead_mount sits on the ceiling of
         * the pocket, midway between the two holes. Z points down, into
         * the head. X runs along the travel, towards the start of the
         * carriage. It joins the frame IF_mount_top of the head, with the
         * joint turned 180 degrees about Z, so the cable points to -X.
         */
        attribute holePitch : LengthValue = 26 [mm];
        attribute screwCount : Natural = 2;
    }

    port def ScaleMountInterface_v2 {
        doc /*
         * The steel tape scale of the linear encoder sticks with its
         * adhesive tape to the inside face of the side wall of the base,
         * on the side of the second rail (y = 17 mm). It needs no end
         * clamps. Stick it on with the RSF TMT Mx 15 MK mounting tool.
         * The wall face must be flat within 0.1 mm and parallel to the
         * guide rails within 0.2 mm (RSF drawing D1158017-04).
         *
         * The tape runs towards -X: its ascending positions point to the
         * end of the base, the same way as the head cable.
         *
         * In the CAD, the frame IF_scale_mount sits on the wall face, at
         * the start of the tape. Z points out of the wall, into the
         * scale. X points to -X. It joins the frame IF_mount_bottom of
         * the scale.
         *
         * Two values of the frame are in the Params sheet of the base.
         * They follow other parts, so change them when those parts
         * change:
         *
         * - x = Params.scale_start_x (361 mm): centres the 240 mm
         *   measuring length on the path of the head sensor between the
         *   two damper contacts (x = 120.8 to 342.8 mm). The tape then
         *   lies from x = 101 to 361 mm, and the measuring length from
         *   x = 111.8 to 351.8 mm.
         * - z = Params.scale_centre_z (34 mm): the sensor line of the
         *   head, 6 mm below the ceiling of its pocket in the carriage.
         *   The tape lies from z = 30 to 38 mm, under the top of the wall
         *   at 40 mm.
         */
    }

    port def ScaleReadInterface_v2 {
        doc /*
         * The read head reads the scale without touching it. The RSF
         * drawing D1158017-04 gives the limits:
         *
         * - the air gap from the top of the tape to the scanning face of
         *   the head is 0.55 +/- 0.25 mm;
         * - the sideways offset of the tape is within +/- 1 mm;
         * - roll, pitch and yaw are each within +/- 20 mrad.
         *
         * In the CAD, the frame IF_scale of the head and the frames
         * IF_ml_start and IF_ml_end of the scale have the same height and
         * the same direction. They differ only along the travel. The
         * assembly gives a gap of 0.55 mm and no sideways offset.
         *
         * Over the travel between the two damper contacts (222 mm), the
         * sensor stays 9 mm inside each end of the 240 mm measuring
         * length. With the dampers fully pressed (236 mm), it stays 2 mm
         * inside each end. The head reads over the full travel.
         */
        attribute gap : LengthValue = 0.55 [mm];
        attribute gapTolerance : LengthValue = 0.25 [mm];
        attribute measuringLength : LengthValue = 240 [mm];
    }

    port def CoolingBlockInterface_v2 {
        doc /*
         * The printed cooling block lies in a 5 mm pocket in the top of
         * carriage-bottom. The pocket has a wide part over the two ends of
         * the cooling channel and an arm with smooth bends to the side face.
         * The arm crosses over the motor cable where the cable comes up.
         * Two ports go from the pocket floor into the channel. A 5 x 1.5
         * NBR 70 O-ring in the bottom of the block seals each port. Three
         * countersunk M2.5 screws come up from below, through
         * carriage-bottom, and are tapped into the block: two in the wide
         * part, one near the side face. All three sit on the centre line of
         * the block.  The motor cable slot is deeper under the arm, with
         * rounded ends, so the cable stays low there.
         *
         * In the CAD, the frame IF_cooling_block sits on the pocket floor,
         * on the axis of screw A (Hole006). Z points up, X and Y as in
         * carriage-bottom. It joins the frame IF_carriage of the block.
         * See docs/decisions/2026-11-09_cooling-block-to-the-edge-with-festo-fittings.md.
         */
        attribute portCount : Natural = 2;
        attribute portDiameter : LengthValue = 2.5 [mm];
        attribute screwCount : Natural = 3;
        attribute pocketDepth : LengthValue = 5 [mm];
        attribute armWidth : LengthValue = 12 [mm];
    }

    port def CableClampInterface_v2 {
        doc /*
         * The end of a cable slot in the top of carriage-bottom, at the
         * side face. Two printed halves with a half-round groove hold the
         * cable there and close the slot end, so almost no dirt gets in.
         * Carriage-top closes the slot. The stack of both halves and the
         * cable is 0.2 mm higher than the slot is deep, so carriage-top
         * presses the cable. Each half is 0.1 mm narrower than the slot on
         * each side, and ends flush with the side face. One for the motor
         * cable, one for the read head cable.
         *
         * In the CAD, the frames IF_motor_cable_clamp and
         * IF_read_head_cable_clamp sit on the slot floor, under the cable
         * axis, in the middle of the clamp length. They join the frame
         * IF_carriage of each clamp.
         */
        attribute squeeze : LengthValue = 0.2 [mm];
        attribute sideGap : LengthValue = 0.1 [mm];
    }

    port def PortSealInterface_v1 {
        doc /*
         * O-ring groove around a cooling port in the bottom face of the
         * cooling block: 8 mm outside, 2 mm wide, 1.1 mm deep, for a 5 x 1.5
         * O-ring. In the CAD, the frames IF_oring_a and IF_oring_b of the
         * block join the frame IF_seat of the O-ring.
         */
        attribute grooveDepth : LengthValue = 1.1 [mm];
    }

    port def FittingPortInterface_v1 {
        doc /*
         * M5 thread tapped in the printed head of the cooling block, 5 mm
         * deep, with 2 mm of resin around it and a flat face for the sealing
         * ring under the hex of the fitting. Tightening torque 1 Nm (Festo
         * data sheet 578334). In the CAD, the frames IF_fitting_a and
         * IF_fitting_b of the block join the frame IF_port of the fitting.
         */
        attribute threadDepth : LengthValue = 5 [mm];
    }

    port def HoseInterface_v1 {
        doc /*
         * Push-in connection for 4 mm tubing, 13 mm insertion depth (Festo
         * data sheet 578334). In the CAD, the frame IF_hose of the fitting
         * joins the frame IF_end of the hose stub.
         */
        attribute tubeOutsideDiameter : LengthValue = 4 [mm];
    }

    port def DamperMountInterface_v1 {
        doc /*
         * End face of carriage-bottom where one TA17-7 damper screws on. M4
         * stud through a 4.5 mm slot into an M4 square nut. The damper axis is
         * Params.damper_axis_z above the bottom face.
         */
    }

    port def DamperStopInterface_v1 {
        doc /*
         * The impact face of one TA17-7 damper hits the back face of a
         * pocket in an end wall of the base. Each pocket is milled from the
         * top of the base: 7 mm deep into the 10 mm wall, 24 mm wide (the
         * damper grows to 22 mm across when fully pressed, ACE manual page
         * 3), inside corners R4 mm, floor at z = 17.5 mm. The sizes are in
         * the Params sheet of the base.
         *
         * In the CAD, the frames IF_damper_a_start_stop and so on sit on
         * the back face of each pocket, on the damper axis. Z points out of
         * the wall, towards the damper.
         */
    }

    port def RollerMountInterface_v1 {
        doc /*
         * The axle of one seal strip roller in its slot in a carriage half.
         * The 2 mm pin lies against the slot wall on the roller centre, and
         * on the slot floor. Two countersunk screws clamp it there.
         *
         * In the CAD, the frames IF_roller_a_start and so on sit on the pin
         * axis, in the middle of the roller. Z points along the pin, towards
         * the b side of the stage.
         */
        attribute axleDiameter : LengthValue = 2 [mm];
        attribute rollerDiameter : LengthValue = 10 [mm];
        attribute rollerLength : LengthValue = 20 [mm];
    }

    port def RollerAxisInterface_v1 {
        doc /*
         * The axis of the roller sleeve, where the pin runs through it. The
         * pin carries the sleeve through the two bearings; it does not touch
         * the sleeve itself. Frame IF_centre on the sleeve and on the pin.
         */
    }

    port def BearingSeatInterface_v1 {
        doc /*
         * One end of the roller sleeve. The bearing sits in the 6 mm hole,
         * and its flange rests on the end face. Frame IF_end_a or IF_end_b on
         * the sleeve, IF_seat on the bearing. Z points out of the sleeve.
         */
        attribute holeDiameter : LengthValue = 6 [mm];
    }

    port def WasherFaceInterface_v1 {
        doc /*
         * The face of a bearing on its flange side, where a washer touches
         * the inner ring. The washer keeps the turning outer ring off the
         * pocket wall. Frame IF_flange_face on the bearing, IF_face on the
         * washer.
         */
    }

    // ---------------------------------------------------------------------
    // Parts. Each port says which side of an interface a part is on.
    // ---------------------------------------------------------------------

    part def Base {
        doc /* The fixed body of the stage. CAD: cad/parts/base/. */
        port machineMount : BaseMountInterface_v1;
        port slotSeal : SlotSealInterface_v1;
        port stripScrews : StripScrewInterface_v1;
        port magnetLongA : MagnetRingInterface_v1;
        port magnetLongB : MagnetRingInterface_v1;
        port magnetStartA1 : MagnetRingInterface_v1;
        port magnetStartA2 : MagnetRingInterface_v1;
        port magnetStartB2 : MagnetRingInterface_v1;
        port magnetStartB1 : MagnetRingInterface_v1;
        port magnetEndA1 : MagnetRingInterface_v1;
        port magnetEndA2 : MagnetRingInterface_v1;
        port magnetEndB2 : MagnetRingInterface_v1;
        port magnetEndB1 : MagnetRingInterface_v1;
        port referenceRailMount : RailMountInterface_v1;
        port secondRailMount : RailMountInterface_v1;
        port firstStatorMount : StatorMountInterface_v1;
        port secondStatorMount : StatorMountInterface_v1;
        port scaleMount : ScaleMountInterface_v2;
        port damperAStartStop : DamperStopInterface_v1;
        port damperBStartStop : DamperStopInterface_v1;
        port damperAEndStop : DamperStopInterface_v1;
        port damperBEndStop : DamperStopInterface_v1;
    }

    part def GuideRail {
        doc /*
         * A bought profile rail: HIWIN EGR15U, 418 mm long (EGR15U418H).
         * It takes the M4 screws of the base. It comes from the parts
         * library in modules/stoq/. The stage has two.
         */
        port baseMount : ~RailMountInterface_v1;
    }

    part def MagnetTrack {
        doc /*
         * A bought magnet track (stator) of the linear motor: Maxwell
         * MK2-180, 180 mm long. It comes from the parts library in
         * modules/stoq/. The stage has two, end to end.
         */
        port mountBottom : ~StatorMountInterface_v1;
    }

    part def CarriageBottom {
        doc /* The moving part inside the base. CAD: cad/parts/carriage-bottom/. */
        port carriageJoint : CarriageJointInterface_v1;
        port blockAStartMount : BlockMountInterface_v1;
        port blockAEndMount : BlockMountInterface_v1;
        port blockBStartMount : BlockMountInterface_v1;
        port blockBEndMount : BlockMountInterface_v1;
        port forcerMount : ForcerMountInterface_v1;
        port readheadMount : ReadheadMountInterface_v2;
        port damperAStartMount : DamperMountInterface_v1;
        port damperBStartMount : DamperMountInterface_v1;
        port damperAEndMount : DamperMountInterface_v1;
        port damperBEndMount : DamperMountInterface_v1;
        port rollerAStart : RollerMountInterface_v1;
        port rollerBStart : RollerMountInterface_v1;
        port rollerAEnd : RollerMountInterface_v1;
        port rollerBEnd : RollerMountInterface_v1;
        port coolingBlock : CoolingBlockInterface_v2;
        port motorCableClamp : CableClampInterface_v2;
        port readHeadCableClamp : CableClampInterface_v2;
    }

    part def GuideBlock {
        doc /*
         * A bought guide block: HIWIN QEH15SAZAP+E2, a light load block
         * with the E2 lubrication unit. It runs on the EGR15U rail. It
         * comes from the parts library in modules/stoq/. The stage has
         * four.
         */
        port mountTop : ~BlockMountInterface_v1;
    }

    part def Forcer {
        doc /*
         * The bought forcer (the coil part) of the linear motor: Maxwell
         * MK21. It runs over the MK2 magnet tracks. It comes from the
         * parts library in modules/stoq/. The stage has one.
         */
        port mountTop : ~ForcerMountInterface_v1;
    }

    part def ReadHead {
        doc /*
         * The bought read head of the linear encoder: RSF AK MC 15 B,
         * absolute, BiSS C, 0.1 um, 36 x 13.5 x 14.8 mm, with a 0.5 m
         * cable out of the end and a 15-pin D-sub connector. Bought:
         * stoq:rsf/mc15-readhead#AK-MC15-B-0.5M-SUBD15. The stage has one.
         */
        port carriageMount : ~ReadheadMountInterface_v2;
        port scaleRead : ~ScaleReadInterface_v2;
    }

    part def Scale {
        doc /*
         * The bought steel tape scale of the linear encoder: RSF MC 15 MK,
         * 240 mm measuring length, 260 mm long, with adhesive tape.
         * Bought: stoq:rsf/mc15-mk-scale#MB-MC15-MK-ML240. The stage has
         * one.
         */
        port baseMount : ~ScaleMountInterface_v2;
        port headRead : ScaleReadInterface_v2;
    }

    part def CarriageTop {
        doc /*
         * The moving part above the base. The load mounts on it.
         * CAD: cad/parts/carriage-top/.
         */
        port loadMount : CarriageMountInterface_v1;
        port carriageJoint : ~CarriageJointInterface_v1;
        port rollerAStart : RollerMountInterface_v1;
        port rollerBStart : RollerMountInterface_v1;
        port rollerAEnd : RollerMountInterface_v1;
        port rollerBEnd : RollerMountInterface_v1;
    }

    part def SealingStrip {
        doc /*
         * Closes the slot in the top of the base. CAD: cad/parts/sealing-strip/.
         *
         * Spring steel strip, EN 1.4310 (AISI 301), 0.15 mm thick. See
         * docs/decisions/2026-10-28_seal-strip-0-15-mm.md.
         */
        attribute thickness : LengthValue = 0.15 [mm];
        port slotSeal : ~SlotSealInterface_v1;
        port stripScrews : ~StripScrewInterface_v1;
    }

    // ---------------------------------------------------------------------
    // The assembly
    // ---------------------------------------------------------------------

    part def CompactStage {
        doc /*
         * The whole compact stage: one design, or one built stage. Fill in
         * the attributes from the CAD model, the data sheets and the
         * measurements. CompactStageSpecification checks them.
         * CAD: cad/assemblies/compact-stage/.
         */

        // Size
        attribute travel : LengthValue;      // usable stroke of the carriage
        attribute width : LengthValue;       // across the direction of motion
        attribute height : LengthValue;      // from the mounting face to the top of the carriage
        attribute length : LengthValue;      // largest length in the direction of motion

        // Accuracy (each value is a half band: +/- this value)
        attribute positioningError : LengthValue;           // systematic and random, uncalibrated
        attribute straightnessError : LengthValue;          // linear error motion across the motion
        attribute flatnessError : LengthValue;              // linear error motion across the motion
        attribute rollError : Real;                         // rad
        attribute pitchError : Real;                        // rad
        attribute yawError : Real;                          // rad
        attribute unidirectionalRepeatability : LengthValue;
        attribute bidirectionalRepeatability : LengthValue;

        // Motion and drive
        attribute maxSpeed : SpeedValue;
        attribute continuousForce : ForceValue;   // driving force along the motion
        attribute peakForce : ForceValue;         // driving force along the motion
        attribute maxOutputPower : PowerValue;    // mechanical: force times speed

        // Load and interfaces
        attribute lateralLoadCapacity : ForceValue;  // at the centre, in either direction
        attribute interfaceHolePitch : LengthValue;  // pitch of the screw holes at each interface

        // End stops (STG-15). No numbers yet: the largest payload is not
        // fixed, and the moving mass must come from the CAD.
        attribute movingMass : MassValue;          // carriage, forcer and read head, without payload
        attribute maxPayload : MassValue;          // largest payload on the carriage that we declare
        attribute motorPushEnergy : EnergyValue;   // limiting force of the motor times the damper stroke
        attribute endStopEnergy : EnergyValue;     // emergency rating of the end stops at one end, together

        part base : Base;
        part carriageBottom : CarriageBottom;
        part carriageTop : CarriageTop;
        part sealingStrip : SealingStrip;
        part magnetLongA : MagnetStrip;
        part magnetLongB : MagnetStrip;
        part magnetStartA1 : MagnetStrip;
        part magnetStartA2 : MagnetStrip;
        part magnetStartB2 : MagnetStrip;
        part magnetStartB1 : MagnetStrip;
        part magnetEndA1 : MagnetStrip;
        part magnetEndA2 : MagnetStrip;
        part magnetEndB2 : MagnetStrip;
        part magnetEndB1 : MagnetStrip;
        part referenceRail : GuideRail;
        part secondRail : GuideRail;
        part firstStator : MagnetTrack;
        part secondStator : MagnetTrack;
        part blockAStart : GuideBlock;
        part blockAEnd : GuideBlock;
        part blockBStart : GuideBlock;
        part blockBEnd : GuideBlock;
        part forcer : Forcer;
        part readHead : ReadHead;
        part scale : Scale;
        part damperAStart : EndStopDamper;
        part damperBStart : EndStopDamper;
        part damperAEnd : EndStopDamper;
        part damperBEnd : EndStopDamper;
        part rollerBottomAStart : SealRoller;
        part rollerBottomBStart : SealRoller;
        part rollerBottomAEnd : SealRoller;
        part rollerBottomBEnd : SealRoller;
        part rollerTopAStart : SealRoller;
        part rollerTopBStart : SealRoller;
        part rollerTopAEnd : SealRoller;
        part rollerTopBEnd : SealRoller;
        part coolingBlock : CoolingBlock;
        part motorCableClamp : CableClamp;
        part readHeadCableClamp : CableClamp;
        part portORingA : PortORing;
        part portORingB : PortORing;
        part fittingA : CoolingFitting;
        part fittingB : CoolingFitting;
        part hoseA : CoolingHose;
        part hoseB : CoolingHose;

        // Interfaces of the whole stage
        port machineMount : BaseMountInterface_v1;
        port loadMount : CarriageMountInterface_v1;
        bind machineMount = base.machineMount;
        bind loadMount = carriageTop.loadMount;

        // The carriage
        connect carriageBottom.carriageJoint to carriageTop.carriageJoint;

        // The seal
        connect base.slotSeal to sealingStrip.slotSeal;
        connect base.stripScrews to sealingStrip.stripScrews;

        // MagnetRing: ten magnet strips in the ring pocket hold the seal strip flat
        connect base.magnetLongA to magnetLongA.ring;
        connect base.magnetLongB to magnetLongB.ring;
        connect base.magnetStartA1 to magnetStartA1.ring;
        connect base.magnetStartA2 to magnetStartA2.ring;
        connect base.magnetStartB2 to magnetStartB2.ring;
        connect base.magnetStartB1 to magnetStartB1.ring;
        connect base.magnetEndA1 to magnetEndA1.ring;
        connect base.magnetEndA2 to magnetEndA2.ring;
        connect base.magnetEndB2 to magnetEndB2.ring;
        connect base.magnetEndB1 to magnetEndB1.ring;

        // The guide rails
        connect base.referenceRailMount to referenceRail.baseMount;
        connect base.secondRailMount to secondRail.baseMount;

        // The magnet tracks of the linear motor
        connect base.firstStatorMount to firstStator.mountBottom;
        connect base.secondStatorMount to secondStator.mountBottom;

        // The guide blocks and the forcer, under the carriage
        connect carriageBottom.blockAStartMount to blockAStart.mountTop;
        connect carriageBottom.blockAEndMount to blockAEnd.mountTop;
        connect carriageBottom.blockBStartMount to blockBStart.mountTop;
        connect carriageBottom.blockBEndMount to blockBEnd.mountTop;
        connect carriageBottom.forcerMount to forcer.mountTop;

        // The linear encoder: the head on the carriage, the scale on the base
        connect carriageBottom.readheadMount to readHead.carriageMount;
        connect base.scaleMount to scale.baseMount;
        connect scale.headRead to readHead.scaleRead;

        // DamperMount: one TA17-7 damper at each corner of the carriage ends
        connect carriageBottom.damperAStartMount to damperAStart.mount;
        connect carriageBottom.damperBStartMount to damperBStart.mount;
        connect carriageBottom.damperAEndMount to damperAEnd.mount;
        connect carriageBottom.damperBEndMount to damperBEnd.mount;

        // DamperStop: each damper hits a pocket in an end wall of the base
        connect base.damperAStartStop to damperAStart.stop;
        connect base.damperBStartStop to damperBStart.stop;
        connect base.damperAEndStop to damperAEnd.stop;
        connect base.damperBEndStop to damperBEnd.stop;

        // RollerMount: four seal strip rollers in each carriage half
        connect carriageBottom.rollerAStart to rollerBottomAStart.axle;
        connect carriageBottom.rollerBStart to rollerBottomBStart.axle;
        connect carriageBottom.rollerAEnd to rollerBottomAEnd.axle;
        connect carriageBottom.rollerBEnd to rollerBottomBEnd.axle;
        connect carriageTop.rollerAStart to rollerTopAStart.axle;
        connect carriageTop.rollerBStart to rollerTopBStart.axle;
        connect carriageTop.rollerAEnd to rollerTopAEnd.axle;
        connect carriageTop.rollerBEnd to rollerTopBEnd.axle;

        // CoolingBlock: the printed block that brings the water from the cooling channel to the side face
        connect carriageBottom.coolingBlock to coolingBlock.carriage;
        connect coolingBlock.portSealA to portORingA.seat;
        connect coolingBlock.portSealB to portORingB.seat;
        connect coolingBlock.fittingPortA to fittingA.port;
        connect coolingBlock.fittingPortB to fittingB.port;
        connect fittingA.hose to hoseA.end;
        connect fittingB.hose to hoseB.end;

        // CableClamp: two printed halves hold each cable where it leaves carriage-bottom
        connect carriageBottom.motorCableClamp to motorCableClamp.carriage;
        connect carriageBottom.readHeadCableClamp to readHeadCableClamp.carriage;
    }

    part def CoolingBlock {
        doc /*
         * The printed cooling block (SLA resin) between the cooling channel
         * in carriage-bottom and the two hoses. Its arm runs to the side
         * face. A head outside the side face holds two Festo push-in
         * fittings NPQH-D-M5-Q4-P10 in M5 threads tapped in the print. CAD:
         * cad/parts/cooling-block/.
         */
        port carriage : ~CoolingBlockInterface_v2;
        port portSealA : PortSealInterface_v1;
        port portSealB : PortSealInterface_v1;
        port fittingPortA : FittingPortInterface_v1;
        port fittingPortB : FittingPortInterface_v1;
    }

    part def CableClamp {
        doc /*
         * A printed cable clamp in two halves with square corners, in the
         * end of a cable slot of carriage-bottom. Carriage-top presses the
         * halves onto the cable.
         * CAD: cad/parts/motor-cable-clamp/ and
         * cad/parts/read-head-cable-clamp/.
         */
        port carriage : ~CableClampInterface_v2;
    }

    part def PortORing {
        doc /*
         * Port O-Ring, bought: stoq:generic/o-ring-metric#5X1.5-NBR70. From
         * the parts library in modules/stoq/.
         */
        port seat : ~PortSealInterface_v1;
    }

    part def CoolingFitting {
        doc /*
         * Cooling Fitting, bought: stoq:festo/npqh#NPQH-D-M5-Q4-P10. From the
         * parts library in modules/stoq/.
         */
        port port : ~FittingPortInterface_v1;
        port hose : HoseInterface_v1;
    }

    part def CoolingHose {
        doc /*
         * Cooling Hose, bought: stoq:festo/pun-h#197383 (Festo
         * PUN-H-4X0,75-BL), sold by the metre. The assembly shows a 20 mm
         * stub at each fitting. From the parts library in modules/stoq/.
         */
        port end : ~HoseInterface_v1;
    }

    part def EndStopDamper {
        doc /*
         * End Stop Damper, bought: stoq:ace/ta-damper#TA17-7. From the parts
         * library in modules/stoq/.
         */
        port mount : ~DamperMountInterface_v1;
        port stop : ~DamperStopInterface_v1;
    }

    part def MagnetStrip {
        doc /*
         * Magnet Strip, bought: neodymium magnet tape 3 x 0.5 mm, cut from
         * the roll stoq:generic/ndfeb-magnet-tape#3X0.5X500. Long strip:
         * stoq:generic/ndfeb-magnet-tape#3X0.5X417.5. Short strip:
         * stoq:generic/ndfeb-magnet-tape#3X0.5X21.5. From the parts library in
         * modules/stoq/. Frame IF_end at a corner of the adhesive face.
         */
        port ring : ~MagnetRingInterface_v1;
    }

    part def SealRoller {
        doc /*
         * One seal strip roller, 10 mm across and 20 mm long. A pin is the
         * fixed axle; two flanged ball bearings carry the sleeve; a washer
         * on each side keeps the bearings off the pocket walls.
         * CAD: cad/assemblies/roller/, frame IF_axle on the pin axis.
         */
        port axle : ~RollerMountInterface_v1;

        part sleeve : RollerSleeve;
        part bearingA : RollerBearing;
        part bearingB : RollerBearing;
        part washerA : RollerWasher;
        part washerB : RollerWasher;
        part pin : RollerAxle;

        connect sleeve.endA to bearingA.seat;
        connect sleeve.endB to bearingB.seat;
        connect bearingA.flangeFace to washerA.face;
        connect bearingB.flangeFace to washerB.face;
        connect sleeve.centre to pin.centre;
    }

    part def RollerSleeve {
        doc /*
         * The sleeve of a seal strip roller: precision tube 10 x 2 mm, cut
         * to 18.4 mm, with a bearing in each end. CAD: cad/parts/roller-sleeve/.
         */
        port centre : RollerAxisInterface_v1;
        port endA : BearingSeatInterface_v1;
        port endB : BearingSeatInterface_v1;
    }

    part def RollerBearing {
        doc /*
         * Roller Bearing, bought: stoq:nsk/miniature-flanged-metric#F692ZZ.
         * From the parts library in modules/stoq/. Two in each roller.
         */
        port seat : ~BearingSeatInterface_v1;
        port flangeFace : WasherFaceInterface_v1;
    }

    part def RollerWasher {
        doc /*
         * Roller Washer, bought: stoq:iso/iso-7092#2-200HV-A2. From the parts
         * library in modules/stoq/. Two in each roller.
         */
        port face : ~WasherFaceInterface_v1;
    }

    part def RollerAxle {
        doc /*
         * Roller Axle, bought: stoq:iso/iso-8734#2X28-A, a 2 x 28 mm hardened
         * dowel pin. From the parts library in modules/stoq/. One in each
         * roller.
         */
        port centre : ~RollerAxisInterface_v1;
    }

    // ---------------------------------------------------------------------
    // Hard requirements. A design that fails one of these is rejected.
    // ---------------------------------------------------------------------

    package Mandatory {

        // --- Size ------------------------------------------------------------

        requirement def <'STG-01'> Width {
            doc /* The stage is at most 210 mm wide. */
            subject stage : CompactStage;
            require constraint { stage.width <= 210 [mm] }
        }

        requirement def <'STG-02'> Height {
            doc /* The stage is at most 60 mm high. */
            subject stage : CompactStage;
            require constraint { stage.height <= 60 [mm] }
        }

        requirement def <'STG-03'> Length {
            doc /*
             * The stage is at most (travel + 340 mm - 2 x height) long.
             *
             * The limit grows with the travel. A lower stage may be longer.
             * Example: a stage with 200 mm travel and 60 mm height may be
             * at most 200 + 340 - 120 = 420 mm long.
             */
            subject stage : CompactStage;
            require constraint {
                stage.length <= stage.travel + 340 [mm] - 2 * stage.height
            }
        }

        // --- Accuracy --------------------------------------------------------

        requirement def <'STG-04'> PositioningError {
            doc /*
             * The total positioning error along the motion is within
             * +/- 5 µm over the full travel. This counts the systematic and
             * the random part together, without any calibration or error
             * table in the controller.
             */
            subject stage : CompactStage;
            require constraint { stage.positioningError <= 5 [µm] }
        }

        requirement def <'STG-05'> LinearErrorMotion {
            doc /*
             * The carriage moves along a straight line within +/- 2 µm, in
             * both directions across the motion. This is the straightness
             * (sideways) and the flatness (up and down) over the full
             * travel. The positioning error along the motion is not part of
             * this requirement: see STG-04.
             */
            subject stage : CompactStage;
            require constraint {
                stage.straightnessError <= 2 [µm] and stage.flatnessError <= 2 [µm]
            }
        }

        requirement def <'STG-06'> RotationalErrorMotion {
            doc /*
             * The carriage tilts and turns by at most +/- 20 µrad over the
             * full travel, about each of the three axes: roll (about the
             * direction of motion), pitch and yaw.
             */
            subject stage : CompactStage;
            require constraint {
                stage.rollError <= 20.0E-6
                and stage.pitchError <= 20.0E-6
                and stage.yawError <= 20.0E-6
            }
        }

        requirement def <'STG-07'> UnidirectionalRepeatability {
            doc /*
             * The carriage returns to the same position within +/- 0.1 µm
             * when it always comes from the same direction.
             */
            subject stage : CompactStage;
            require constraint { stage.unidirectionalRepeatability <= 0.1 [µm] }
        }

        requirement def <'STG-08'> BidirectionalRepeatability {
            doc /*
             * The carriage returns to the same position within +/- 0.3 µm
             * when it comes from either direction. This includes the
             * backlash and the hysteresis of the stage.
             */
            subject stage : CompactStage;
            require constraint { stage.bidirectionalRepeatability <= 0.3 [µm] }
        }

        // --- Motion and drive -------------------------------------------------

        requirement def <'STG-09'> MaxSpeed {
            doc /*
             * The carriage reaches at least 3 m/s.
             *
             * The drive requirements in motor-drive.sysml use this speed.
             * The encoder frequency (DRV-08) and the bus voltage (DRV-04)
             * follow from it.
             */
            subject stage : CompactStage;
            require constraint { stage.maxSpeed >= 3 [m/s] }
        }

        requirement def <'STG-10'> ContinuousForce {
            doc /*
             * The stage pushes the carriage with at least 180 N without a
             * time limit.
             */
            subject stage : CompactStage;
            require constraint { stage.continuousForce >= 180 [N] }
        }

        requirement def <'STG-11'> PeakForce {
            doc /* The stage pushes the carriage with at least 500 N at its peak. */
            subject stage : CompactStage;
            require constraint { stage.peakForce >= 500 [N] }
        }

        requirement def <'STG-12'> OutputPower {
            doc /*
             * The stage gives at least 100 W of mechanical output power:
             * driving force times speed.
             */
            subject stage : CompactStage;
            require constraint { stage.maxOutputPower >= 100 [W] }
        }

        // --- Load and interfaces ----------------------------------------------

        requirement def <'STG-13'> LateralLoad {
            doc /*
             * The carriage carries a sideways load of at least 500 N at the
             * centre of the carriage, in either direction across the motion.
             */
            subject stage : CompactStage;
            require constraint { stage.lateralLoadCapacity >= 500 [N] }
        }

        requirement def <'STG-14'> InterfaceGrid {
            doc /*
             * The screw holes at each mechanical interface fit a grid of
             * 20 mm, 40 mm or 80 mm. The hole pitch is a whole multiple of
             * 20 mm, so the stage mounts on the same grid as other parts.
             */
            subject stage : CompactStage;
            require constraint {
                stage.interfaceHolePitch == 20 [mm]
                or stage.interfaceHolePitch == 40 [mm]
                or stage.interfaceHolePitch == 80 [mm]
            }
        }

        // --- Safety -------------------------------------------------------------

        requirement def <'STG-15'> EndStopEnergy {
            doc /*
             * The end stops at each end stop the carriage with the largest
             * payload at the top speed (STG-09), while the motor still
             * pushes, within their emergency rating.
             *
             * The stage has no limit switches. The software limits of the
             * drive are not a safety function, so the end stops are the last
             * protection when the carriage runs away. The motor push is the
             * limiting force of the motor over the damper stroke: 670 N times
             * 7 mm, about 4.7 J for two ACE TA17-7.
             *
             * Today two TA17-7 per end give 18 J in an emergency. The moving
             * mass without payload is about 4.2 kg (estimate from the CAD;
             * weigh it). With no payload this allows a speed limit of about
             * 2.3 m/s, not 3 m/s. The table "Largest payload against the
             * speed limit" in docs/compact-stage-ce-assessment.md gives the
             * speed limit to set and lock in the drive for each payload.
             */
            subject stage : CompactStage;
            require constraint {
                0.5 * (stage.movingMass + stage.maxPayload) * stage.maxSpeed * stage.maxSpeed
                    + stage.motorPushEnergy <= stage.endStopEnergy
            }
        }
    }

    // ---------------------------------------------------------------------
    // The full set, for one stage
    // ---------------------------------------------------------------------

    requirement def CompactStageSpecification {
        doc /*
         * All requirements for one compact stage. A design passes
         * when it meets every mandatory requirement.
         */
        subject stage : CompactStage;

        requirement width : Mandatory::Width;
        requirement height : Mandatory::Height;
        requirement length : Mandatory::Length;
        requirement positioningError : Mandatory::PositioningError;
        requirement linearErrorMotion : Mandatory::LinearErrorMotion;
        requirement rotationalErrorMotion : Mandatory::RotationalErrorMotion;
        requirement unidirectionalRepeatability : Mandatory::UnidirectionalRepeatability;
        requirement bidirectionalRepeatability : Mandatory::BidirectionalRepeatability;
        requirement maxSpeed : Mandatory::MaxSpeed;
        requirement continuousForce : Mandatory::ContinuousForce;
        requirement peakForce : Mandatory::PeakForce;
        requirement outputPower : Mandatory::OutputPower;
        requirement lateralLoad : Mandatory::LateralLoad;
        requirement interfaceGrid : Mandatory::InterfaceGrid;
        requirement endStopEnergy : Mandatory::EndStopEnergy;
    }
}
